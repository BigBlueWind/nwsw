-- @file    SON-CONFIG-MIB.txt
 -- @section Copyright Powerwave Technologies, Inc., 2010
 --
 -- Author: Powerwave
 -- Generated on : 10/1/2012 5:40:51 PM
 --

SON-CONFIG-MIB DEFINITIONS ::= BEGIN

IMPORTS
       lte, ProfileId                                    FROM LTE-MIB
       OBJECT-TYPE, MODULE-IDENTITY, Unsigned32          FROM SNMPv2-SMI;

sonConfig MODULE-IDENTITY
       LAST-UPDATED "201103021852Z"
       ORGANIZATION
              "Powerwave Technologies Inc."
       CONTACT-INFO
              "Powerwave Technologies Inc.
               pwregistry@pwav.com"
       DESCRIPTION
              "Contains configuration parameters for SON (Self Organising Networks) Features of ENB."
       REVISION   "201103021852Z"
       DESCRIPTION "Initial Version."
::= { lte 67 }

sonConfigTable OBJECT-TYPE
       SYNTAX      SEQUENCE OF SonConfigEntry
       MAX-ACCESS  not-accessible
       STATUS      current
       DESCRIPTION
           "Contains configuration parameters for SON (Self Organising Networks) Features of ENB.
            This is a SINGLE ROW Table"
       ::= { sonConfig 1 }

sonConfigEntry OBJECT-TYPE
       SYNTAX      SonConfigEntry
       MAX-ACCESS  not-accessible
       STATUS      current
       DESCRIPTION
             "An entry defines a profile of SON configuration."
       INDEX  { sonProfileId }
       ::= { sonConfigTable 1 }

SonConfigEntry ::= 
   SEQUENCE {
       sonProfileId              ProfileId,
       intraFreqHoThreshold      Unsigned32,
       icicThreshold             Unsigned32,
       ueLoadChangeThreshold     Unsigned32
   }

sonProfileId OBJECT-TYPE
       SYNTAX      ProfileId
       MAX-ACCESS  read-write
       STATUS      current
       DESCRIPTION
           "[Parameter_Description :
             Identifies a profile. Profiles are a mechanism for grouping configuration.]
           [Change_Condition : RW ]"
       DEFVAL { 1 }
       ::= { sonConfigEntry 1 }

intraFreqHoThreshold OBJECT-TYPE
       SYNTAX      Unsigned32 ( 0 .. 12 )
       MAX-ACCESS  read-write
       STATUS      current
       DESCRIPTION
           "[Parameter_Description :
             This parameter specified the threshold in dB for classifying intra-frequency measurements for Handover Management]
           [Change_Condition : RW ]"
       DEFVAL { 2 }
       ::= { sonConfigEntry 2 }

icicThreshold OBJECT-TYPE
       SYNTAX      Unsigned32 ( 0 .. 12 )
       MAX-ACCESS  read-write
       STATUS      current
       DESCRIPTION
           "[Parameter_Description :
             This parameter specifies the threshold (in dB) for classifying intra-frequency  measurements for ICIC. It is also used for main interferer identification]
           [Change_Condition : RW ]"
       DEFVAL { 5 }
       ::= { sonConfigEntry 3 }

ueLoadChangeThreshold OBJECT-TYPE
       SYNTAX      Unsigned32 ( 0 .. 100 )
       MAX-ACCESS  read-write
       STATUS      current
       DESCRIPTION
           "[Parameter_Description :
             This parameter specifies the threshold (in percent) of UE load change beyond which the eNB should update the EMS of its new statistics]
           [Change_Condition : RW ]"
       DEFVAL { 25 }
       ::= { sonConfigEntry 4 }

END
