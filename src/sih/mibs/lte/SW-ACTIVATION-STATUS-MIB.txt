-- @file    SW-ACTIVATION-STATUS-MIB.txt
 -- @section Copyright Powerwave Technologies, Inc., 2010
 --
 -- Author: Powerwave
 -- Generated on : 10/1/2012 5:40:48 PM
 --

SW-ACTIVATION-STATUS-MIB DEFINITIONS ::= BEGIN

IMPORTS
       lte, RowNumber, VersionString, OperationStatus          FROM LTE-MIB
       OBJECT-TYPE, MODULE-IDENTITY                            FROM SNMPv2-SMI;

swActivationStatus MODULE-IDENTITY
       LAST-UPDATED "201103021852Z"
       ORGANIZATION
              "Powerwave Technologies Inc."
       CONTACT-INFO
              "Powerwave Technologies Inc.
               pwregistry@pwav.com"
       DESCRIPTION
              "Displays the status of SW Activation"
       REVISION   "201103021852Z"
       DESCRIPTION "Initial Version."
::= { lte 103 }

swActivationStatusTable OBJECT-TYPE
       SYNTAX      SEQUENCE OF SwActivationStatusEntry
       MAX-ACCESS  not-accessible
       STATUS      current
       DESCRIPTION
           "Displays the status of SW Activation
            This is a SINGLE ROW Table"
       ::= { swActivationStatus 1 }

swActivationStatusEntry OBJECT-TYPE
       SYNTAX      SwActivationStatusEntry
       MAX-ACCESS  not-accessible
       STATUS      current
       DESCRIPTION
             "An entry which contains list of software activation configuration objects."
       INDEX  { swStatus }
       ::= { swActivationStatusTable 1 }

SwActivationStatusEntry ::= 
   SEQUENCE {
       index        RowNumber,
       version      VersionString,
       swStatus     OperationStatus
   }

index OBJECT-TYPE
       SYNTAX      RowNumber
       MAX-ACCESS  read-only
       STATUS      current
       DESCRIPTION
           "[Parameter_Description :
             Unique identifier of row]"
       ::= { swActivationStatusEntry 1 }

version OBJECT-TYPE
       SYNTAX      VersionString
       MAX-ACCESS  read-only
       STATUS      current
       DESCRIPTION
           "[Parameter_Description :
             Version of the software that was to be activated (release.revision.bugfix.vendor.svnversion)]"
       ::= { swActivationStatusEntry 2 }

swStatus OBJECT-TYPE
       SYNTAX      OperationStatus
       MAX-ACCESS  read-only
       STATUS      current
       DESCRIPTION
           "[Parameter_Description :
             Status of the processing of the last received software activation request
             notInitiated: No software activation request has been received till now
             inProgress: Last received software activation procedure is under progress
             successful: activation was successful and BS is now running that version (NOTIFY_SW_ACT_SUCC)
             failed: activation failed. BS has fallen back to the previous version (NOTIFY_SW_ACT_FAIL)
             In both cases, a notification is generated by BS]"
       ::= { swActivationStatusEntry 3 }

END
