ENB-NON-ALARM-NOTIFICATION-MIB DEFINITIONS ::= BEGIN

IMPORTS
   lte, swType, dateAndTimeStamp, fileName, errorInfo, oamIfType, productId, notificationSequenceNumber, enodebId, version     FROM LTE-MIB
   NOTIFICATION-TYPE, MODULE-IDENTITY                                                                                          FROM SNMPv2-SMI
   TEXTUAL-CONVENTION                                                                                                          FROM SNMPv2-TC
   cellId                                                                                                                      FROM CELL-ADMIN-MIB
   profileId                                                                                                                   FROM COUNTER-CONTROL-MIB
   cellId                                                                                                                      FROM CELL-CONFIG-MIB
   mmeIpAddr                                                                                                                   FROM MME-CONFIG-MIB
   profileId                                                                                                                   FROM COUNTER-CONFIG-MIB
   operationalState, adminState                                                                                                FROM ENB-STATUS-MIB
   longitude, latitude                                                                                                         FROM LOCATION-STATUS-MIB
   cellId                                                                                                                      FROM RRC-CELL-COUNTERS-MIB
   cellId                                                                                                                      FROM CELL-STATUS-MIB
   profileId, stoppedReason                                                                                                    FROM COUNTER-COLLECTION-STATUS-MIB;

enbNonAlarmNotificationsMib MODULE-IDENTITY
       LAST-UPDATED "201103021852Z"
       ORGANIZATION
              "Powerwave Technologies Inc."
       CONTACT-INFO
              "Powerwave Technologies Inc.
               pwregistry@pwav.com"
       DESCRIPTION
        "The EnodeB Notifications MIB describes the 
         Notifications generated by EnodeB that are not alarms
         Alarms are described in ENB-ALARM-MIB.txt."
       REVISION   "201103021852Z"
       DESCRIPTION
        "Initial Version."
       ::= { lte 501 }

-- Textual Conventions

-- Object Identifiers
enbNonAlarmNotificationsObjects  OBJECT IDENTIFIER ::= { enbNonAlarmNotificationsMib 0 }
enbNonAlarmNotifications         OBJECT IDENTIFIER ::= { enbNonAlarmNotificationsMib 1 }

-- Objects

-- Non-Alarm Notification
mmeReset NOTIFICATION-TYPE
      OBJECTS {
        enodebId,
        notificationSequenceNumber,
        dateAndTimeStamp,
        mmeIpAddr
      }
      STATUS  current
      DESCRIPTION
       "Generated when ENB receives S1AP: RESET from MME.
        mmeId - identifies the MME that sent reset."
      ::= { enbNonAlarmNotifications 1 }

fileUploadCompleted NOTIFICATION-TYPE
      OBJECTS {
        enodebId,
        notificationSequenceNumber,
        dateAndTimeStamp,
        fileName
      }
      STATUS  current
      DESCRIPTION
       "Generated when file uploading from ENB completes successfully.
        fileName - the file that was uploaded from ENB."
      ::= { enbNonAlarmNotifications 2 }

fileUploadFailed  NOTIFICATION-TYPE
      OBJECTS {
        enodebId,
        notificationSequenceNumber,
        dateAndTimeStamp,
        fileName,
        errorInfo
      }
      STATUS  current
      DESCRIPTION
       "Generated when file uploading from ENB fails.
        fileName - the file that was being uploaded from ENB
        errorInfo - error details"
      ::= { enbNonAlarmNotifications 3 }

fileDownloadCompleted  NOTIFICATION-TYPE
      OBJECTS {
        enodebId,
        notificationSequenceNumber,
        dateAndTimeStamp,
        fileName
      }
      STATUS  current
      DESCRIPTION
       "Generated when file downloading to ENB completes successfully.
        fileName - the file that was downloaded to EnodeB"
      ::= { enbNonAlarmNotifications 4 }

fileDownloadFailed  NOTIFICATION-TYPE
      OBJECTS {
        enodebId,
        notificationSequenceNumber,
        dateAndTimeStamp,
        fileName,
        errorInfo
      }
      STATUS  current
      DESCRIPTION
       "Generated when file downloading to ENB fails.
        fileName - the file whose download was affected
        errorInfo - error details"
      ::= { enbNonAlarmNotifications 5 }

messageTraceCompleted  NOTIFICATION-TYPE
      OBJECTS {
        enodebId,
        notificationSequenceNumber,
        dateAndTimeStamp,
        fileName
      }
      STATUS  current
      DESCRIPTION
       "Generated when message tracing on ENB completes.
        fileName - the file containing the traces"
      ::= { enbNonAlarmNotifications 6 }

messageTraceFailed  NOTIFICATION-TYPE
      OBJECTS {
        enodebId,
        notificationSequenceNumber,
        dateAndTimeStamp,
        errorInfo
      }
      STATUS  current
      DESCRIPTION
       "Generated when message tracing on ENB fails.
        errorInfo - details the error"
      ::= { enbNonAlarmNotifications 7 }

counterFileAvailable  NOTIFICATION-TYPE
      OBJECTS {
        enodebId,
        notificationSequenceNumber,
        dateAndTimeStamp,
        fileName
      }
      STATUS  current
      DESCRIPTION
       "Generated when a file containing performance counters is available.
        fileName - the file containing the counters"
      ::= { enbNonAlarmNotifications 8 }

counterCollectionFailed  NOTIFICATION-TYPE
      OBJECTS {
        enodebId,
        notificationSequenceNumber,
        dateAndTimeStamp,
        errorInfo
      }
      STATUS  current
      DESCRIPTION
       "Generated when a performance counter collection fails.
        pmProfileId - the PM profile under which the counters were being collected
        errorInfo - details the error"
      ::= { enbNonAlarmNotifications 9 }

configurationChanged  NOTIFICATION-TYPE
      OBJECTS {
        enodebId,
        notificationSequenceNumber,
        dateAndTimeStamp,
        oamIfType
      }
      STATUS  current
      DESCRIPTION
       "Generated when EnodeB configuration is changed via a non-EMS OAM interface.
        enodebId - identifies the enodeb that generated this event
        dateAndTimeStamp - the date and time when it happened
        oamIf - the oam interface from which the config was changed
        eg: CLI, Web-Craft"
      ::= { enbNonAlarmNotifications 10 }

configurationSaved NOTIFICATION-TYPE
      OBJECTS {
        enodebId,
        notificationSequenceNumber,
        dateAndTimeStamp,
        oamIfType
      }
      STATUS  current
      DESCRIPTION
       "Generated when EnodeB configuration is saved in the persistent memory by
        a non-EMS OAM interface.
        enodebId - identifies the enodeb that generated this event
        dateAndTimeStamp - the date and time when it happened
        oamIf - the oam interface from which the config was saved
        eg: CLI, Web-Craft"
      ::= { enbNonAlarmNotifications 11 }

configurationRollBack NOTIFICATION-TYPE
      OBJECTS {
        enodebId,
        notificationSequenceNumber,
        dateAndTimeStamp,
        oamIfType
      }
      STATUS  current
      DESCRIPTION
       "Generated when EnodeB configuration is rolled-back from persistent memory by
        a non-EMS OAM interface.
        enodebId - identifies the enodeb that generated this event
        dateAndTimeStamp - the date and time when it happened  
        oamIf - the oam interface from which the config was rolled back
        eg: CLI, Web-Craft"
      ::= { enbNonAlarmNotifications 12 }

swActivationFailed  NOTIFICATION-TYPE
      OBJECTS {
        enodebId,
        notificationSequenceNumber,
        dateAndTimeStamp,
        swType,
        version,
        errorInfo
      }
      STATUS  current
      DESCRIPTION
       "Generated when the software switch-over to 'version' failed.
        EnodeB had fallen back to the previously running version.
        swType - the type of software package to be activated
        version - the version that was requesed to be activated
        errorInfo - describes the error encountered during activation"
      ::= { enbNonAlarmNotifications 13 }

swActivationSuccess  NOTIFICATION-TYPE
      OBJECTS {
        enodebId,
        notificationSequenceNumber,
        dateAndTimeStamp,
        swType,
        version
      }
      STATUS  current
      DESCRIPTION
       "Generated when the software switch-over to 'version' is successful.
        swType - the type of software package to be activated
        version - the version that was activated and is now running"
      ::= { enbNonAlarmNotifications 14 }

swInstallFailed  NOTIFICATION-TYPE
      OBJECTS {
        enodebId,
        notificationSequenceNumber,
        dateAndTimeStamp,
        fileName,
        errorInfo
      }
      STATUS  current
      DESCRIPTION
       "Generated when software install procedure fails.
        installedFileName: the file that was being installed
        installerName: the installer program installing the file
        errorCode: identifies the error that was encoutered during installation
        errorInfo: details of the error"
      ::= { enbNonAlarmNotifications 15 }

swInstallSuccess  NOTIFICATION-TYPE
      OBJECTS {
        enodebId,
        notificationSequenceNumber,
        dateAndTimeStamp,
        fileName,
        version
      }
      STATUS  current
      DESCRIPTION
       "Generated when software install procedure completes successfully.
        fileName: the package-file that was installed
        version: the version of the software, contained in the package installed"
      ::= { enbNonAlarmNotifications 16 }

enbRegistrationReq  NOTIFICATION-TYPE
      OBJECTS {
        enodebId,
        notificationSequenceNumber,
        dateAndTimeStamp,
        productId,
        longitude,
        latitude
      }
      STATUS  current
      DESCRIPTION
       "Generated when ENB wants to register with EMS."
      ::= { enbNonAlarmNotifications 17 }

enbOperationalStateChanged NOTIFICATION-TYPE
      OBJECTS {
        enodebId,
        notificationSequenceNumber,
        dateAndTimeStamp,
        operationalState
      }
      STATUS  current
      DESCRIPTION
       "Generated when operational state of the ENB is changed.
        operationalState: disabled / enabled towards providing service."
      ::= { enbNonAlarmNotifications 18 }

enbAdminStateChanged NOTIFICATION-TYPE
      OBJECTS {
        enodebId,
        notificationSequenceNumber,
        dateAndTimeStamp,
        adminState
      }
      STATUS  current
      DESCRIPTION
       "Generated when administrative state of the ENB is changed.
        adminState: locked / unlocked towards providing service."
      ::= { enbNonAlarmNotifications 19 }

enbLocationChanged NOTIFICATION-TYPE
      OBJECTS {
        enodebId,
        notificationSequenceNumber,
        dateAndTimeStamp,
        longitude,
        latitude
      }
      STATUS  current
      DESCRIPTION
       "Generated when location coordinates of the ENB is changed.
        latitude: New Latitude Value.
        longitude: New Longitude Value."
      ::= { enbNonAlarmNotifications 20 }

noNeighborConfigured NOTIFICATION-TYPE
      OBJECTS {
        enodebId,
        notificationSequenceNumber,
        dateAndTimeStamp
      }
      STATUS  current
      DESCRIPTION
       "Generated when No Neighbors are configured for the ENB 
        getting unlocked."
      ::= { enbNonAlarmNotifications 21 }

cellBarredInd NOTIFICATION-TYPE
      OBJECTS {
        enodebId,
        notificationSequenceNumber,
        cellId,
        dateAndTimeStamp
      }
      STATUS  current
      DESCRIPTION
       "Generated when Cell is barred, that can be operator ititiated or ENB initiated"
      ::= { enbNonAlarmNotifications 22 }

cellUnBarredInd NOTIFICATION-TYPE
      OBJECTS {
        enodebId,
        notificationSequenceNumber,
        cellId,
        dateAndTimeStamp
      }
      STATUS  current
      DESCRIPTION
       "Generated when Cell is barred, that can be operator ititiated or ENB initiated"
      ::= { enbNonAlarmNotifications 23 }

measurementCompleted NOTIFICATION-TYPE
      OBJECTS {
        enodebId,
        notificationSequenceNumber,
        dateAndTimeStamp,
        profileId,
        stoppedReason
      }
      STATUS  current
      DESCRIPTION
       "Generated when Measurement completed for any profile
        profileId: ProfileId for which measuremet has been completed.
        Reason: why measurement has been completed"
      ::= { enbNonAlarmNotifications 24 }

END
