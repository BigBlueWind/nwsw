-- @file    FILE-UPLOAD-STATUS-MIB.txt
 -- @section Copyright Powerwave Technologies, Inc., 2010
 --
 -- Author: Powerwave
 -- Generated on : 10/1/2012 5:40:48 PM
 --

FILE-UPLOAD-STATUS-MIB DEFINITIONS ::= BEGIN

IMPORTS
       lte, RowNumber, String256, FileUploadCommand, OperationStatus, Percentage          FROM LTE-MIB
       OBJECT-TYPE, MODULE-IDENTITY                                                       FROM SNMPv2-SMI;

fileUploadStatus MODULE-IDENTITY
       LAST-UPDATED "201103021852Z"
       ORGANIZATION
              "Powerwave Technologies Inc."
       CONTACT-INFO
              "Powerwave Technologies Inc.
               pwregistry@pwav.com"
       DESCRIPTION
              "Allows operator to see the status of last file-upload"
       REVISION   "201103021852Z"
       DESCRIPTION "Initial Version."
::= { lte 102 }

fileUploadStatusTable OBJECT-TYPE
       SYNTAX      SEQUENCE OF FileUploadStatusEntry
       MAX-ACCESS  not-accessible
       STATUS      current
       DESCRIPTION
           "Allows operator to see the status of last file-upload
            This is a SINGLE ROW Table"
       ::= { fileUploadStatus 1 }

fileUploadStatusEntry OBJECT-TYPE
       SYNTAX      FileUploadStatusEntry
       MAX-ACCESS  not-accessible
       STATUS      current
       DESCRIPTION
             "An entry containing information applicable to a 
particular file upload status."
       INDEX  { index }
       ::= { fileUploadStatusTable 1 }

FileUploadStatusEntry ::= 
   SEQUENCE {
       index                         RowNumber,
       fileUploadCommandReceived     FileUploadCommand,
       fileName                      String256,
       uploadStatus                  OperationStatus,
       percentageComplete            Percentage
   }

index OBJECT-TYPE
       SYNTAX      RowNumber
       MAX-ACCESS  read-only
       STATUS      current
       DESCRIPTION
           "[Parameter_Description :
             Unique identifier of row]"
       ::= { fileUploadStatusEntry 1 }

fileUploadCommandReceived OBJECT-TYPE
       SYNTAX      FileUploadCommand
       MAX-ACCESS  read-only
       STATUS      current
       DESCRIPTION
           "[Parameter_Description :
             Command for file upload request from operator]"
       ::= { fileUploadStatusEntry 2 }

fileName OBJECT-TYPE
       SYNTAX      String256
       MAX-ACCESS  read-only
       STATUS      current
       DESCRIPTION
           "[Parameter_Description :
             File that was to be uploaded]"
       ::= { fileUploadStatusEntry 3 }

uploadStatus OBJECT-TYPE
       SYNTAX      OperationStatus
       MAX-ACCESS  read-only
       STATUS      current
       DESCRIPTION
           "[Parameter_Description :
             Status of the processing of the last received file upload request
             ongoing: procedure is still going on. percentageComplete indicates the how has been uploaded.
             successful: upload is complete. A notification is generated by BS on completeion. (NOTIFY_FILE_UPLOAD_SUCC)
             failed: upload could not be completed successfully.  A notification is generated by BS on failure (ALARM_FILE_UPLOAD_FAIL)]"
       ::= { fileUploadStatusEntry 4 }

percentageComplete OBJECT-TYPE
       SYNTAX      Percentage
       MAX-ACCESS  read-only
       STATUS      current
       DESCRIPTION
           "[Parameter_Description :
             Percentage of file that has been uploaded]"
       ::= { fileUploadStatusEntry 5 }

END
